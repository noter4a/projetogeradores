GENERATOR-MIB DEFINITIONS ::= BEGIN

-- MIB for the native SNMP agent in server/src/services/snmp-agent.js.
-- Troque 99999 pelo seu Private Enterprise Number (PEN), registrado de graca
-- em https://pen.iana.org/pen/PenApplication.page, antes de entregar isso a
-- um cliente externo. O agente tambem le SNMP_ENTERPRISE_OID do .env — troque
-- os dois juntos (o numero aqui e so documentacao; quem manda no OID real
-- servido pela rede e a env var).

IMPORTS
    MODULE-IDENTITY, OBJECT-TYPE, NOTIFICATION-TYPE, enterprises
        FROM SNMPv2-SMI;

generatorGateway MODULE-IDENTITY
    LAST-UPDATED "202608100000Z"
    ORGANIZATION "Sua Empresa"
    CONTACT-INFO "seu-email@empresa.com"
    DESCRIPTION
        "MIB do agente SNMP nativo de monitoramento de geradores (Ciklo)."
    ::= { enterprises 99999 }

-- Tabela conceitual: uma linha por gerador, indexada por generatorIndex
-- (inteiro estavel, atribuido na primeira vez que o gerador e visto pelo
-- agente e mantido pelo tempo de vida do processo — nao e o mesmo id que
-- aparece no painel).
generatorTable OBJECT-TYPE
    SYNTAX      SEQUENCE OF GeneratorEntry
    MAX-ACCESS  not-accessible
    STATUS      current
    DESCRIPTION
        "Tabela com uma linha por gerador monitorado."
    ::= { generatorGateway 1 }

generatorEntry OBJECT-TYPE
    SYNTAX      GeneratorEntry
    MAX-ACCESS  not-accessible
    STATUS      current
    DESCRIPTION "Uma linha da tabela de geradores."
    INDEX       { generatorIndex }
    ::= { generatorTable 1 }

GeneratorEntry ::= SEQUENCE {
    generatorIndex      Integer32,
    generatorId         OCTET STRING,
    generatorName       OCTET STRING,
    statusCode          INTEGER,
    connected           INTEGER,
    mainsVoltageL1      Gauge32,
    mainsVoltageL2      Gauge32,
    mainsVoltageL3      Gauge32,
    genVoltageL1        Gauge32,
    genVoltageL2        Gauge32,
    genVoltageL3        Gauge32,
    mainsCurrentL1      Gauge32,
    mainsCurrentL2      Gauge32,
    mainsCurrentL3      Gauge32,
    genCurrentL1        Gauge32,
    genCurrentL2        Gauge32,
    genCurrentL3        Gauge32,
    frequency           Gauge32,
    rpm                 Gauge32,
    fuelLevel           Gauge32,
    batteryVoltage      Gauge32,
    oilPressure         Gauge32,
    engineTemp          Gauge32,
    activePower         Gauge32,
    alarmCode           Integer32,
    runHours            Gauge32,
    lastUpdateEpoch     Gauge32
}

generatorIndex OBJECT-TYPE
    SYNTAX      Integer32 (1..2147483647)
    MAX-ACCESS  read-only
    STATUS      current
    DESCRIPTION "Indice estavel da linha (nao e o ID do gerador no painel)."
    ::= { generatorEntry 1 }

generatorId OBJECT-TYPE
    SYNTAX      OCTET STRING
    MAX-ACCESS  read-only
    STATUS      current
    DESCRIPTION "ID do gerador como aparece no banco/painel (ex: GEN-172...)."
    ::= { generatorEntry 2 }

generatorName OBJECT-TYPE
    SYNTAX      OCTET STRING
    MAX-ACCESS  read-only
    STATUS      current
    DESCRIPTION "Nome cadastrado do gerador."
    ::= { generatorEntry 3 }

statusCode OBJECT-TYPE
    SYNTAX      INTEGER { stopped(1), running(2), alarm(3), offline(4) }
    MAX-ACCESS  read-only
    STATUS      current
    DESCRIPTION "Status atual do gerador."
    ::= { generatorEntry 4 }

connected OBJECT-TYPE
    SYNTAX      INTEGER { no(0), yes(1) }
    MAX-ACCESS  read-only
    STATUS      current
    DESCRIPTION "Se o gerador reportou dados nos ultimos 120s."
    ::= { generatorEntry 5 }

-- RENUMERADO em 2026-08-10: a v1 desta MIB (colunas 1-17) so tinha a fase 1
-- de tensao, com L2/L3 e as correntes penduradas no final (18-27) pra nao
-- quebrar o cliente que ja consumia a v1 em producao. Dessa vez o cliente vai
-- reconfigurar do lado dele, entao a tabela foi reagrupada de vez: tensao
-- junto com tensao, corrente junto com corrente, cada uma com L1/L2/L3 em
-- sequencia. Numero de coluna a partir da 6 mudou em relacao a v1 — qualquer
-- integracao externa precisa atualizar os OIDs que consulta.

mainsVoltageL1 OBJECT-TYPE
    SYNTAX      Gauge32
    MAX-ACCESS  read-only
    STATUS      current
    DESCRIPTION "Tensao da rede eletrica, fase 1 (V)."
    ::= { generatorEntry 6 }

mainsVoltageL2 OBJECT-TYPE
    SYNTAX      Gauge32
    MAX-ACCESS  read-only
    STATUS      current
    DESCRIPTION "Tensao da rede eletrica, fase 2 (V)."
    ::= { generatorEntry 7 }

mainsVoltageL3 OBJECT-TYPE
    SYNTAX      Gauge32
    MAX-ACCESS  read-only
    STATUS      current
    DESCRIPTION "Tensao da rede eletrica, fase 3 (V)."
    ::= { generatorEntry 8 }

genVoltageL1 OBJECT-TYPE
    SYNTAX      Gauge32
    MAX-ACCESS  read-only
    STATUS      current
    DESCRIPTION "Tensao gerada pelo grupo gerador, fase 1 (V)."
    ::= { generatorEntry 9 }

genVoltageL2 OBJECT-TYPE
    SYNTAX      Gauge32
    MAX-ACCESS  read-only
    STATUS      current
    DESCRIPTION "Tensao gerada pelo grupo gerador, fase 2 (V)."
    ::= { generatorEntry 10 }

genVoltageL3 OBJECT-TYPE
    SYNTAX      Gauge32
    MAX-ACCESS  read-only
    STATUS      current
    DESCRIPTION "Tensao gerada pelo grupo gerador, fase 3 (V)."
    ::= { generatorEntry 11 }

mainsCurrentL1 OBJECT-TYPE
    SYNTAX      Gauge32
    MAX-ACCESS  read-only
    STATUS      current
    DESCRIPTION "Corrente da rede eletrica, fase 1, em A x10 (152 = 15.2A)."
    ::= { generatorEntry 12 }

mainsCurrentL2 OBJECT-TYPE
    SYNTAX      Gauge32
    MAX-ACCESS  read-only
    STATUS      current
    DESCRIPTION "Corrente da rede eletrica, fase 2, em A x10 (152 = 15.2A)."
    ::= { generatorEntry 13 }

mainsCurrentL3 OBJECT-TYPE
    SYNTAX      Gauge32
    MAX-ACCESS  read-only
    STATUS      current
    DESCRIPTION "Corrente da rede eletrica, fase 3, em A x10 (152 = 15.2A)."
    ::= { generatorEntry 14 }

genCurrentL1 OBJECT-TYPE
    SYNTAX      Gauge32
    MAX-ACCESS  read-only
    STATUS      current
    DESCRIPTION "Corrente do grupo gerador, fase 1, em A x10 (152 = 15.2A)."
    ::= { generatorEntry 15 }

genCurrentL2 OBJECT-TYPE
    SYNTAX      Gauge32
    MAX-ACCESS  read-only
    STATUS      current
    DESCRIPTION "Corrente do grupo gerador, fase 2, em A x10 (152 = 15.2A)."
    ::= { generatorEntry 16 }

genCurrentL3 OBJECT-TYPE
    SYNTAX      Gauge32
    MAX-ACCESS  read-only
    STATUS      current
    DESCRIPTION "Corrente do grupo gerador, fase 3, em A x10 (152 = 15.2A)."
    ::= { generatorEntry 17 }

frequency OBJECT-TYPE
    SYNTAX      Gauge32
    MAX-ACCESS  read-only
    STATUS      current
    DESCRIPTION "Frequencia do gerador, em Hz x10 (600 = 60.0 Hz)."
    ::= { generatorEntry 18 }

rpm OBJECT-TYPE
    SYNTAX      Gauge32
    MAX-ACCESS  read-only
    STATUS      current
    DESCRIPTION "Rotacao do motor (RPM)."
    ::= { generatorEntry 19 }

fuelLevel OBJECT-TYPE
    SYNTAX      Gauge32
    MAX-ACCESS  read-only
    STATUS      current
    DESCRIPTION "Nivel de combustivel (%)."
    ::= { generatorEntry 20 }

batteryVoltage OBJECT-TYPE
    SYNTAX      Gauge32
    MAX-ACCESS  read-only
    STATUS      current
    DESCRIPTION "Tensao da bateria de partida, em V x10 (272 = 27.2V)."
    ::= { generatorEntry 21 }

oilPressure OBJECT-TYPE
    SYNTAX      Gauge32
    MAX-ACCESS  read-only
    STATUS      current
    DESCRIPTION "Pressao do oleo, em bar x100 (550 = 5.50 bar)."
    ::= { generatorEntry 22 }

engineTemp OBJECT-TYPE
    SYNTAX      Gauge32
    MAX-ACCESS  read-only
    STATUS      current
    DESCRIPTION "Temperatura do motor/liquido de arrefecimento (graus C)."
    ::= { generatorEntry 23 }

activePower OBJECT-TYPE
    SYNTAX      Gauge32
    MAX-ACCESS  read-only
    STATUS      current
    DESCRIPTION "Potencia ativa, em kW x10 (453 = 45.3 kW)."
    ::= { generatorEntry 24 }

alarmCode OBJECT-TYPE
    SYNTAX      Integer32
    MAX-ACCESS  read-only
    STATUS      current
    DESCRIPTION "Codigo do alarme atualmente ativo (0 = sem alarme)."
    ::= { generatorEntry 25 }

runHours OBJECT-TYPE
    SYNTAX      Gauge32
    MAX-ACCESS  read-only
    STATUS      current
    DESCRIPTION "Horimetro total, em horas x100 (9666 = 96.66h)."
    ::= { generatorEntry 26 }

lastUpdateEpoch OBJECT-TYPE
    SYNTAX      Gauge32
    MAX-ACCESS  read-only
    STATUS      current
    DESCRIPTION "Timestamp Unix (segundos) da ultima leitura recebida."
    ::= { generatorEntry 27 }

-- Notificacoes (traps). Disparadas pelo agente (nao fazem parte da tabela)
-- quando alarmCode de um gerador muda de valor entre um ciclo de poll e
-- outro — inicio de alarme (0 -> N), troca de alarme (N -> M) ou resolucao
-- (N -> 0). So enviado se SNMP_TRAP_TARGET / SNMP_CLIENT_EXPORT_<n>_TRAP_TARGET
-- estiver configurado — ver server/SNMP.md.

notifications OBJECT IDENTIFIER ::= { generatorGateway 2 }

alarmTrap NOTIFICATION-TYPE
    OBJECTS { trapGeneratorId, trapGeneratorName, trapPreviousAlarmCode,
              trapCurrentAlarmCode, trapEventType }
    STATUS  current
    DESCRIPTION
        "Disparado quando o alarme ativo de um gerador muda de estado."
    ::= { notifications 1 }

trapVars OBJECT IDENTIFIER ::= { generatorGateway 3 }

trapGeneratorId OBJECT-TYPE
    SYNTAX      OCTET STRING
    MAX-ACCESS  accessible-for-notify
    STATUS      current
    DESCRIPTION "ID do gerador cujo alarme mudou (mesmo valor de generatorId)."
    ::= { trapVars 1 }

trapGeneratorName OBJECT-TYPE
    SYNTAX      OCTET STRING
    MAX-ACCESS  accessible-for-notify
    STATUS      current
    DESCRIPTION "Nome do gerador cujo alarme mudou."
    ::= { trapVars 2 }

trapPreviousAlarmCode OBJECT-TYPE
    SYNTAX      Integer32
    MAX-ACCESS  accessible-for-notify
    STATUS      current
    DESCRIPTION "Codigo de alarme antes da mudanca (0 = nao tinha alarme)."
    ::= { trapVars 3 }

trapCurrentAlarmCode OBJECT-TYPE
    SYNTAX      Integer32
    MAX-ACCESS  accessible-for-notify
    STATUS      current
    DESCRIPTION "Codigo de alarme depois da mudanca (0 = alarme resolvido)."
    ::= { trapVars 4 }

trapEventType OBJECT-TYPE
    SYNTAX      OCTET STRING
    MAX-ACCESS  accessible-for-notify
    STATUS      current
    DESCRIPTION "STARTED, CHANGED ou CLEARED."
    ::= { trapVars 5 }

END
